// AUTO-GENERATED from requirements/00_terminology.md by
// tools/requirements/md_to_trlc.py — do not edit by hand.

package HSMCPP

Term TERM_Initialization {
  term       = "Initialization"
  definition = "The operation that transitions a configured state machine from the configuration phase into an executing state. After initialization, the initial state is active and events can be processed."
  context    = "State Machine Lifecycle"
}

Term TERM_Release {
  term       = "Release"
  definition = "The operation that terminates execution and returns the state machine to a configurable state. After release, the state machine does not process events until re-initialized."
  context    = "State Machine Lifecycle"
}

Term TERM_Active_state_configuration {
  term       = "Active state configuration"
  definition = "The set of states that are currently active in a state machine at any point during execution. In a flat state machine this is a single state; with hierarchy it includes the active state at each level; with parallel regions it includes the active state in each region."
  context    = "State Machine Lifecycle"
}

Term TERM_Event {
  term       = "Event"
  definition = "A uniquely identified stimulus that can trigger state transitions."
  context    = "Events"
}

Term TERM_Externally_submitted_event {
  term       = "Externally submitted event"
  definition = "An event submitted by application code through the library's event submission interface."
  context    = "Events"
}

Term TERM_Internally_generated_event {
  term       = "Internally generated event"
  definition = "An event generated by the library itself during processing, including events from declarative actions (automatic event generation), final state completion events, and timer expiration events."
  context    = "Events"
}

Term TERM_Transition_request {
  term       = "Transition request"
  definition = "A request submitted to the state machine to process a specified event, potentially causing a state change."
  context    = "Transitions"
}

Term TERM_Transition {
  term       = "Transition"
  definition = "The process of changing the active state configuration in response to an event, including execution of associated callbacks."
  context    = "Transitions"
}

Term TERM_Successful_transition {
  term       = "Successful transition"
  definition = "A transition that completes the full callback sequence without cancellation, resulting in the target state becoming active."
  context    = "Transitions"
}

Term TERM_Cancelled_transition {
  term       = "Cancelled transition"
  definition = "A transition that is terminated by a cancellable callback (exit or entry) before the target state becomes active. The active state configuration is restored to its pre-transition state."
  context    = "Transitions"
}

Term TERM_Failed_transition {
  term       = "Failed transition"
  definition = "A transition request that cannot be processed because no matching transition exists for the event in the current active state configuration, or because all matching transitions have unsatisfied guard conditions."
  context    = "Transitions"
}

Term TERM_Cancellable_callback {
  term       = "Cancellable callback"
  definition = "A callback that can terminate the transition in progress by returning a cancellation indication. Exit callbacks and entry callbacks are cancellable."
  context    = "Callbacks"
}

Term TERM_Non_cancellable_callback {
  term       = "Non-cancellable callback"
  definition = "A callback that cannot terminate the transition. State-changed callbacks and transition callbacks are non-cancellable."
  context    = "Callbacks"
}

Term TERM_Timer_expiration_event {
  term       = "Timer expiration event"
  definition = "An internally generated event produced when a timer's configured interval elapses."
  context    = "Timers"
}

Term TERM_Single_shot_timer {
  term       = "Single-shot timer"
  definition = "A timer that generates one expiration event and then stops automatically."
  context    = "Timers"
}

Term TERM_Repeating_timer {
  term       = "Repeating timer"
  definition = "A timer that generates periodic expiration events at a configured interval until explicitly stopped."
  context    = "Timers"
}
